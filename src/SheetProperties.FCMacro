# SheetProperties.FCMacro
# LGPL license; Copyright (C) 2018 Uri Benchetrit

"""
Spreadsheet Cells Properties Actions                         |
"""

__title__ = "SheetPropertiesActions"
__author__ = "Uri Benchetrit, <uribench@gmail.com>"
__version__ = "1.0.7"
__date__ = "2020-12-19"

__Comment__ = "FreeCAD Macro for manipulating properties of spreadsheet cells"

__Wiki__ = "TBD"
__Help__ = "See the README.md file"
__Status__ = "stable"
__Requires__ = "FreeCAD 0.18"

from SheetProperties.activeDocumentSheets import ActiveDocumentSheets
from SheetProperties.sheetPropertiesActionsForm import SheetPropertiesActionsForm
from SheetProperties.preconditionError import PreconditionError

def main():
    """Entry point"""

    try:
        context = ActiveDocumentSheets()
    except PreconditionError as e:
        print('Preconditions check failed (Reason: {0})'.format(e.reason))
        return None

    # Note: the SheetPropertiesActionsForm, may be destroyed by the Python
    # interpreter's garbage collector if a reference to it is not maintained.
    return SheetPropertiesActionsForm(context)

# -----------------------------------------------------------------------
# Entry point
# -----------------------------------------------------------------------

# execute main() only if this code is run as a script and not if imported as a module.
if __name__ == "__main__":
    form = main()   # maintain a reference to the main window
                    # to avoid a premature garbage collection
